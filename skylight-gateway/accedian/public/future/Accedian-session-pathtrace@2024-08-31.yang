module Accedian-session-pathtrace {
  yang-version 1.1;
  namespace "http://accedian.com/ns/yang/session/pathtrace";
  prefix acdspt;

  import ietf-inet-types {
    prefix inet;
  }

  import Accedian-net-type {
    prefix acdnt;
  }

  import Accedian-session {
    prefix acdses;
  }

  import Accedian-session-type {
    prefix acdstype;
  }

  organization
    "Accedian Networks Inc.";
  contact
    "Accedian Networks Inc.

    https://accedian.com/
    Email: info@accedian.com

    2351 Blvd Alfred-Nobel, Suite N-410
    Saint-Laurent (Montreal), Quebec,
    H4S 2A9, Canada

    Phone: +1.514.331.6181 or +1.866.685.8181";

  description
    "The pathtrace session type implements a path
    trace (traceroute) client for testing reachability
    and layer-3-path from the test agent towards a
    service or destination.

    Copyright (c) Accedian Networks, Inc.
    All rights reserved";

  revision 2024-08-31 {
    description
      "Initial revision";
  }

  augment "/acdses:sessions/acdses:session/acdses:service-endpoints/acdses:session-protocol" {
    when "derived-from-or-self(/acdses:sessions/acdses:session/acdses:session-type, 'acdstype:pathtrace-session')" {
      description
        "Augment the service session protocol of Accedian-service-session with pathtrace
        config data";
    }

    container pathtrace {
      description
        "This session type tracks the route packets takes from an IP network on their
        way to a given host. It utilizes the IP protocol's time to live (TTL) field
        and attempts to elicit an ICMP TIME_EXCEEDED response from each gateway along
        the path to the host";

      leaf probing-rate {
        type uint8 {
          range "1..99";
        }
        units seconds;
        default 10;
        description
          "Probing rate";
      }

      leaf probes-per-hop {
        type uint8 {
          range "1..255";
        }
        default 3;
        description
          "Number of probes sent per hop";
      }

      leaf max-undiscovered {
        type uint8 {
          range "1..255";
        }
        units hops;
        default 3;
        description
          "Maximum number of consecutive unresponsive hops causing test abort";
      }

      leaf wait-time {
        type uint32;
        units seconds;
        default 5;
        description
          "Time to wait for a probe response";
      }

      leaf test-duration {
        type uint32;
        units seconds;
        default 180;
        description
          "Timeout of the measurement.
          Pass 0 to set it to infinity";
      }

      leaf algorithm {
        description
          "The traceroute algorithm to use";
        type enumeration {
          enum paris-traceroute {
            description
              "Paris traceroute is a new version of the well-known
              network diagnosis and measurement tool. It addresses
              problems caused by load balancers with the initial
              implementation of traceroute.";
            reference "https://paris-traceroute.net/";
          }
        }
        default paris-traceroute;
      }

      leaf transport-type {
        type enumeration {
          enum udp;
          enum icmp;
          enum tcp;
        }
        default udp;
        description
          "Trace transport type";
      }

      container session-sender {
        description
          "Configuration data for the pathtrace generator";

        leaf admin-state {
          type boolean;
          default false;
          description
            "Indicates whether the associated session
            endpoint is operating as a pathtrace packet
            generator";
        }

        container test-packets {
          description
            "The configuration of the packets transmitted by
            the session generator";

          leaf source-port {
            type acdnt:source-port-number;
            description
              "The UDP source port number that is to be used by
              the Session-Sender for this pathtrace session";
          }

          leaf start-ttl {
            type uint8 {
              range "0..255";
            }
            default 1;
            description
              "Start the first probe from this TTL";
          }

          leaf end-ttl {
            type uint8 {
              range "0..255";
            }
            default 30;
            description
              "Set the last probe with this TTL";
          }

          leaf dscp {
            type acdnt:dscp;
            description
              "DSCP value used by the IP probes";
          }
        }
      }

      container session-reflector {
        description
          "Configuration data of the pathtrace destination";

        leaf admin-state {
          type boolean;
          default false;
          description
            "Indicates whether the associated session
            endpoint is operating as a pathtrace destination";
        }

        leaf destination-ip {
          type inet:ip-address;
          mandatory true;
          description
            "The IP address of destination. If not specified, the
            address configured in the associated service-session-endpoint
            will be used. If a peered endpoint is not defined or if
            the peer doesn't specify an address, an error will be
            returned";
        }

        leaf destination-port {
          type inet:port-number;
          default 33457;
          description
            "Port number of the reflector";
        }
      }
    }
  }
}
