module Accedian-session-transfer {
  yang-version 1.1;
  namespace "http://accedian.com/ns/yang/session/transfer";
  prefix acdtransf;

  import ietf-inet-types {
    prefix inet;
  }

  import Accedian-session {
    prefix acdses;
  }

  import Accedian-session-type {
    prefix acdstype;
  }

  organization
    "Accedian Networks Inc.";
  contact
    "Accedian Networks Inc.

    https://accedian.com/
    Email: info@accedian.com

    2351 Blvd Alfred-Nobel, Suite N-410
    Saint-Laurent (Montreal), Quebec,
    H4S 2A9, Canada

    Phone: +1.514.331.6181 or +1.866.685.8181";

  description
    "The transfer session type implements a TCP and HTTP(s)/FTP
    client for testing availability and responsiveness of services.

    Copyright (c) Accedian Networks, Inc.
    All rights reserved";

  revision 2024-08-31 {
    description
      "Initial revision";
  }

  augment "/acdses:sessions/acdses:session/acdses:service-endpoints/acdses:session-protocol" {
    when "derived-from-or-self(/acdses:sessions/acdses:session/acdses:session-type, 'acdstype:transfer')";
    description
      "Augment the service session protocol of Accedian-service-session with
      the config data for a transfer session";

    container transfer {
      description
        "Transfer session configuration";

      leaf max-test-connection {
        type uint32;
        default 20;
        description
          "Timeout in seconds of the measurement connection (pass 0 to set it to infinity)";
      }

      leaf max-test-duration {
        type int32;
        default 180;
        description
          "Timeout in seconds of the measurement (pass 0 to set it to infinity)";
      }

      leaf test-interval {
        type uint32 {
          range "1..max";
        }
        default 60;
        description
          "Test repeat interval in seconds";
      }

      container session-sender {
        description
          "Transfer session packet generator configuration data";

        leaf admin-state {
          type boolean;
          default false;
          description
            "Indicates whether the associated session
            endpoint is operating as a transfer test
            packet generator";
        }

        leaf use-proxy {
          type boolean;
          default false;
          description
            "Set to true to configure a proxy";
        }

        container proxy {
          when "../use-proxy = 'true'";
          description
            "Proxy configuration";

          leaf proxy-destination {
            type inet:host;
            description
              "IPv4 address, IPv6 address or FQDN of http(s) proxy";
          }

          leaf proxy-port {
            type uint16;
            default 33457;
            description
              "Proxy destination port number";
          }

          leaf proxy-username {
            type string;
            description
              "http(s) proxy auth user name";
          }

          leaf proxy-password {
            type string;
            description
              "http(s) proxy auth password";
          }

          leaf name-server {
            type inet:host;
            description
              "IPv4 address, IPv6 address of name server optionally override system default";
          }

          leaf force-ip-version {
            type inet:ip-version;
            description
              "Override session to configured IP version";
          }
        }

        container session-reflector {
          description
            "Transfer session packet destination configuration data";

          leaf admin-state {
            type boolean;
            default false;
            description
              "Indicates whether the associated session
              endpoint is operating as a throughput destination";
          }

          leaf destination-url {
            type inet:host;
            mandatory true;
            description
              "URL with IPv4 address, IPv6 address or FQDN port number and path";
          }

          leaf username {
            type string;
            description
              "http(s) basic auth user name";
          }

          leaf password {
            type string;
            description
              "http(s) basic auth password";
          }
        }
      }
    }
  }
}
