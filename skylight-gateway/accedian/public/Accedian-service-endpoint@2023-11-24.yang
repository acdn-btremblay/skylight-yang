module Accedian-service-endpoint {
  yang-version 1.1;
  namespace "http://accedian.com/ns/yang/service/endpoint";
  prefix acdsep;

  import Accedian-type {
    prefix acdt;
  }

  import Accedian-service-endpoint-type {
    prefix acdsept;
  }

  import Accedian-session-type {
    prefix acdst;
  }

  import Accedian-extensions {
    prefix acdext;
  }

  organization
    "Accedian Networks Inc.";
  contact
    "Accedian Networks Inc.

    https://accedian.com/
    Email: info@accedian.com

    2351 Blvd Alfred-Nobel, Suite N-410
    Saint-Laurent (Montreal), Quebec,
    H4S 2A9, Canada

    Phone: +1.514.331.6181 or +1.866.685.8181";

  description
    "This module contains the definition of a Accedian service endpoint.

    Copyright (c) Accedian Networks, Inc.
    All rights reserved";

  revision 2023-11-24 {
    description
      "Augment the capability definition to be able to provde per session-type capabilities";
  }

  revision 2023-06-23 {
    description
      "Add the endpoint group-id field";
  }

  revision 2023-02-10 {
    description
      "Initial revision";
  }

  notification state-change-event {
    description
      "This notification is sent when the state of the endpoint changes";

    leaf endpoint-id {
      type acdt:id;
      description
        "An identifier specifying on which endpoint the state-change happened. This leaf
        will match the name of an existing endpoint-id";
    }

    leaf group-id {
      type acdt:id;
      description
        "The value of the Group ID configured in
        Accedian-service-endpoint:service-endpoints:service-endpoint:group-id.
        The value will be present only if the value was configured in the service-endpoint
        associated with state-change-event:endpoint-id";
    }

    uses acdsept:service-endpoint-state-data;
  }

  container service-endpoints {
    list service-endpoint {
      description
        "The list of all service enpoints currently configured. Provides the config and state  of
        each service endpoint";
      key endpoint-id;
      unique endpoint-name;

      leaf endpoint-id {
        type acdt:id;
        acdext:tag-metadata endpoint_id;
        description
          "The endpoint unique identifier.
          tag-metadata: This leaf will be included as part of the analytics
          metadata as { endpoint_id : <endpoint-id> }";
      }

      leaf endpoint-name {
        type acdt:id;
        acdext:tag-metadata endpoint_name;
        description
          "An optional human readable endpoint name. When provided, the field must
          be unique through all the 'list service-endpoint' instances.
          'endpoint-name' can be used as an extra metadata query parameter in
          analytics in addition to the endpoint-id. It can also be configured
          to query more easily the analytics when the endpoint-id is in non-human
          readble form (numerical, UUIDs, etc...).
          tag-metadata: This leaf will be included as part of the analytics
          metadata as { endpoint_name : <endpoint-name> }";
      }

      leaf group-id {
        type acdt:id;
        description
          "An optional group identifier that associates this endpoint to a logical group of
          endpoints. The yang client can associate an endpoint to a group of endpoints by configuring
          the same group-id in all the endpointss belonging to that group. These groupings can then
          be used to perform operations on all endpoints belonging to a group. It can also be used to
          register to event stream resources based on the group-id";
      }


      leaf description {
        type string;
        description
          "An optional human readable description for this endpoint";
      }

      leaf type {
        type identityref {
          base acdsept:service-endpoint;
        }
        description
          "The type of service of this sessions";
      }

      container config {
        description
          "Endpoint specific configuration for this endpoint. The configuration is
          dependent on the service-endpoint type specified in endpoint-type.
          It is implemented as a Yang augment mount point";
      }

      container state {
        description
          "Defines the state information that can be retrieved for a service endpoint";
        config false;

        leaf version {
          type string;
          description
            "This leaf indicates the version of the service-endpoint.
            The format of the version is service endpoint specific";
        }

        list capabilities {
          description
            "List of session types supported by the endpoint";

          leaf session-type {
            type identityref {
              base acdst:session;
            }
            description
              "Indicated the session types supported by this endpoint";
          }

          container session-capabilities  {
            description
              "A session type specific list of supported capabilities. Since the capabilities
              are dependent on the session type, it is augmented as a Yang augment mount point";
          }
        }

        container status {
          uses acdsept:service-endpoint-state-data;
        }
      }
    }
  }
}
