module Accedian-service-l3vpn {
  yang-version 1.1;
  namespace "http://accedian.com/ns/yang/service/l3vpn";
  prefix acdsl3vpn;

  import Accedian-service {
    prefix acdserv;
  }

  import Accedian-service-type {
    prefix acdservt;
  }

  organization
    "Accedian Networks Inc.";
  contact
    "Accedian Networks Inc.

    https://accedian.com/
    Email: info@accedian.com

    2351 Blvd Alfred-Nobel, Suite N-410
    Saint-Laurent (Montreal), Quebec,
    H4S 2A9, Canada

    Phone: +1.514.331.6181 or +1.866.685.8181";

  description
    "This module defines a L3VPN service. It
    augment the definition of the top level service
    module Accedian-service.yang.

    Copyright (c) Accedian Networks, Inc.
    All rights reserved";

  revision 2023-02-10 {
    description
      "Initial revision ";
  }

  augment "/acdserv:services/acdserv:service/acdserv:service-definition" {
    when "/acdserv:services/acdserv:service/acdserv:type = 'acdservt:l3vpn'" {

      description
        "Augment Accedian service with l3vpn support";
    }

    container l3vpn-config {
      description
        "Contains L3VPN configuration data";
    }
  }
}
