module Accedian-service-endpoint-agent {
  yang-version 1.1;
  namespace "http://accedian.com/ns/yang/service/endpoint/agent";
  prefix acdsepagt;

  import Accedian-service-endpoint-type {
    prefix acdsept;
  }

  import Accedian-service-endpoint {
    prefix acdsep;
  }

  organization
    "Accedian Networks Inc.";
  contact
    "Accedian Networks Inc.

    https://accedian.com/
    Email: info@accedian.com

    2351 Blvd Alfred-Nobel, Suite N-410
    Saint-Laurent (Montreal), Quebec,
    H4S 2A9, Canada

    Phone: +1.514.331.6181 or +1.866.685.8181";

  description
    "This module contains the definition of a Accedian Agent endpoint.
    It augments the definition of the top level Accedian endpoint.

    Copyright (c) Accedian Networks, Inc.
    All rights reserved";

  revision 2022-10-25 {
    description
      "Initial revision";
  }

  augment "/acdsep:service-endpoints/acdsep:service-endpoint/acdsep:config" {
    when "/acdsep:service-endpoints/acdsep:service-endpoint/acdsep:type = 'acdsept:agent-endpoint'" {
      description
        "Augment Accedian-service-endpoint data with agents support";
    }

    container agent-config {
      leaf agent-id {
        type string;
        description
          "Agent UUID identifier";
      }
    }
  }
}
