module Accedian-session-echo {
  yang-version 1.1;
  namespace "http://accedian.com/ns/yang/session/echo";
  prefix acdsecho;

  import ietf-inet-types {
    prefix inet;
  }

  import Accedian-session {
    prefix acdses;
  }

  import Accedian-session-type {
    prefix acdstype;
  }

  organization
    "Accedian Networks Inc.";
  contact
    "Accedian Networks Inc.

    https://accedian.com/
    Email: info@accedian.com

    2351 Blvd Alfred-Nobel, Suite N-410
    Saint-Laurent (Montreal), Quebec,
    H4S 2A9, Canada

    Phone: +1.514.331.6181 or +1.866.685.8181";

  description
    "TODO.

    Copyright (c) Accedian Networks, Inc.
    All rights reserved";

  revision 2022-10-25 {
    description
      "Initial revision";
  }

  augment "/acdses:sessions/acdses:session/acdses:service-endpoints/acdses:session-protocol" {
    when "/acdses:sessions/acdses:session/acdses:session-type = 'acdstype:echo-session'";
    description
      "Augment the service session protocol of Accedian-service-session with echo
      config data";

    container echo {

      container sender {
        leaf addr {
          type inet:host;
          description
            "Echo sender address or FQDN, defaults to Docker IP address";
        }

        leaf port {
          type inet:port-number;
          description
            "UDP port number, default generated by agent";
        }

        leaf payload-size {
          type uint16 {
            range 20..1472;
          }
          default 82;
          description
            "Echo payload size in bytes";
        }

        leaf rate {
          type uint16 {
            range 1..1000;
          }
          default 10;
          description
            "Echo packet rate in PPS";
        }

        leaf dscp {
          type inet:dscp;
          default 0;
          description
            "Echo sender DSCP value";
        }

        leaf ttl {
          type uint8 {
            range 0..255;
          }
          default 255;
          description
            "Echo sender TTL value";
        }

        leaf vprio {
          type uint8 {
            range 0..7;
          }
          default 0;
          description
            "Echo sender VLAN prio";
        }
      }

      container reflector {
        leaf addr {
          type string;
          description
            "Echo reflector IPv4 address or FQDN";
        }

        leaf port {
          type inet:port-number;
          default 7;
          description
            "Echo UDP reflector port number";
        }

        leaf report-interval {
          type uint16 {
            range 1..900;
          }
          default 30;
          description
            "Reporting interval in seconds";
        }
      }
    }
  }
}
