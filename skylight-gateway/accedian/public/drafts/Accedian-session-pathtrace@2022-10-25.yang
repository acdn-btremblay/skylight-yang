module Accedian-session-pathtrace {
  yang-version 1.1;
  namespace "http://accedian.com/ns/yang/session/pathtrace";
  prefix acdspt;

  import ietf-inet-types {
    prefix inet;
  }

  import Accedian-session {
    prefix acdses;
  }

  import Accedian-session-type {
    prefix acdstype;
  }

  organization
    "Accedian Networks Inc.";
  contact
    "Accedian Networks Inc.

    https://accedian.com/
    Email: info@accedian.com

    2351 Blvd Alfred-Nobel, Suite N-410
    Saint-Laurent (Montreal), Quebec,
    H4S 2A9, Canada

    Phone: +1.514.331.6181 or +1.866.685.8181";

  description
    "TODO.

    Copyright (c) Accedian Networks, Inc.
    All rights reserved";

  revision 2022-10-25 {
    description
      "Initial revision";
  }


  augment "/acdses:sessions/acdses:session/acdses:service-endpoints/acdses:session-protocol" {
    when "/acdses:sessions/acdses:session/acdses:session-type = 'acdstype:pathtrace-session'" {
      description
        "Augment the service session protocol of Accedian-service-session with pathtrace
        config data";
    }

    container pathtrace {
      leaf port {
        type inet:port-number;
      }

      leaf destination {
        type inet:host;
        description
          "Trace address";
      }

      leaf destination-port {
        type inet:port-number;
        default 33457;
        description
          "Destination port number";
      }

      leaf sender-port {
        type inet:port-number;
        default 33456;
        description
          "Sender port number";
      }

      leaf ip-version {
        type inet:ip-version;
        default ipv4;
        description
          "Version of IP. By default, the agent automatically detects the IP version";
      }

      leaf algorithm {
        type string;
        default "paris-traceroute";
        description
          "Trace algoritm";
      }

      leaf type {
        type enumeration {
          enum udp;
          enum icmp;
          enum tcp;
        }
        default udp;
        description
          "Trace type";
      }

      leaf probing-rate {
        type uint8 {
          range 1..99;
        }
        default 10;
        description
          "Probing rate. Probes per second";
      }

      leaf sender-ttl-min {
        type uint8 {
          range 1..255;
        }
        default 1;
        description
          "Start the first probe from this TTL instead of 1";
      }

      leaf sender-ttl-max {
        type uint8 {
          range 1..255;
        }
        default 30;
        description
          "Set the max number of hops to be reached";
      }

      leaf sender-dscp {
        type inet:dscp;
        default 0;
        description
          "DSCP value used by the IP probes";
      }

      leaf probes-per-hop {
        type uint8 {
          range 1..255;
        }
        default 3;
        description
          "Number of probes sent per hop";
      }

      leaf max-undiscovered {
        type uint8 {
          range 1..255;
        }
        default 3;
        description
          "Maximum number of consecutive unresponsive hops causing test abort";
      }

      leaf wait-sec {
        type uint32;
        default 5;
        description
          "Number of seconds to wait for a probe response";
      }

      leaf test-duration-sec {
        type uint32;
        default 180;
        description
          "Timeout in seconds of the measurement (pass 0 to set it to infinity)";
      }
    }
  }
}
