module Accedian-sat-capabilities {
  yang-version 1.1;
  namespace "http://accedian.com/ns/yang/session/cap/sat";
  prefix acdsc;

  import Accedian-session-type {
    prefix acdst;
  }

  import Accedian-service-endpoint {
    prefix acdsep;
  }

  organization
    "Accedian Networks Inc.";
  contact
    "Accedian Networks Inc.

    https://accedian.com/
    Email: info@accedian.com

    2351 Blvd Alfred-Nobel, Suite N-410
    Saint-Laurent (Montreal), Quebec,
    H4S 2A9, Canada

    Phone: +1.514.331.6181 or +1.866.685.8181";

  description
    "This module contains the type definitions of SAT capabilities.

    Copyright (c) Accedian Networks, Inc.
    All rights reserved";

  revision 2023-11-24 {
    description
      "Initial revision";
  }

  augment "/acdsep:service-endpoints/acdsep:service-endpoint/acdsep:state/acdsep:capabilities/acdsep:session-capabilities" {
    when "/acdsep:service-endpoints/acdsep:service-endpoint/acdsep:state/acdsep:capabilities/acdsep:session-type = 'acdst:sat'" {

      description
        "Augment Accedian service-endpoint capabilities with SAT specific capabilities";
    }

    container sat-capabilities {
      description
        "SAT specific capabilities";

      list capability {
        key capability-key;
        description
          "List of key-value where each entry represents a SAT capability and it's corresponding value. The type
          of each value is key specific and is described in the key description";

        leaf capability-key {
          description
            "A leaf representing a SAT capability. The meaning of each capability and its value
            is described in the following enumeraton";

          type enumeration {
            enum "RFC2544" {
              description
                "Boolean key to indicate if the endpoint can perform SAT tests using RFC2544";
            }

            enum "ITU-Y.1564" {
              description
                "Boolean key to indicate if the endpoint can perform SAT tests using ITU-Y.1564";
            }
          }
        }

        leaf capability-value {
          description
            "The value associated with each SAT capability key. The value depends on the
            key. The value type is provided in the key description";
          type acdst:capability-value;
        }
      }
    }
  }
}
