module Accedian-session-twamp-light {
  yang-version 1.1;
  namespace "http://accedian.com/ns/yang/session/twamp/light";
  prefix acdstwl;

  import ietf-inet-types {
    prefix inet;
  }

  import Accedian-session {
    prefix acdses;
  }

  import Accedian-session-type {
    prefix acdstype;
  }

  organization
    "Accedian Networks Inc.";
  contact
    "Accedian Networks Inc.

    https://accedian.com/
    Email: info@accedian.com

    2351 Blvd Alfred-Nobel, Suite N-410
    Saint-Laurent (Montreal), Quebec,
    H4S 2A9, Canada

    Phone: +1.514.331.6181 or +1.866.685.8181";

  description
    "This module contains the definition of an Accedian TWAMP Light
    session protocol.

    Accedian TWAMP Light defines a simpler version of the RFC5357
    TWAMP protocol. It differs mainly by eliminating the need for
    the TWAMP-Control protocol. Some other notable differences are:
    - Since the control protocol is ommited, the configuration of
    both the session-sender and session-reflector is done through a
    static configuration.
    - The Session-Reflector does not have knowledge of the session
    state. Because of this, the Session-Reflector will copy the
    Sequence Number of the received packet to the Sequence Number field
    of the reflected packet.

    Copyright (c) Accedian Networks, Inc.
    All rights reserved";

  revision 2023-02-10 {
    description
      "Initial revision";
  }

  feature session-sender {
    description
      "Indicates that the device supports configuration of the
      TWAMP Session-Sender logical entity";
  }

  feature session-reflector {
    description
      "Indicates that the device supports configuration of the
      TWAMP Session-Reflector logical entity";
  }

  typedef reflector-mode {
    description
      "The modes of operation of the TWAMP Light reflector";
    type enumeration {
      enum "stateless" {
        description
          "In stateless mode, the reflector does not have a sequence numbers so only
          round-trip packet domain metrics are reported";
      }
      enum "stateful" {
        description
          "In stateful mode, the reflector provides a separate series of sequence numbers for
          the return packets. Metrics (for packet loss, reorder and duplication) are
          reported separately for the uplink and downlink directions";
      }
    }
  }

  augment "/acdses:sessions/acdses:session/acdses:service-endpoints/acdses:session-protocol" {
    when "derived-from-or-self(/acdses:sessions/acdses:session/acdses:session-type, 'acdstype:twamp-light-session')";
    description
      "Augment the service session protocol of Accedian-service-session with twamp light
      config data";

    container twamp-light {

      container session-sender {
        if-feature "session-sender";
        description
          "Configuration of the TWAMP Session-Sender logical entity";

        leaf admin-state {
          type boolean;
          default false;
          description
            "Indicates whether the device is allowed to operate
            as a TWAMP session-sender";
        }

        leaf sender-ip {
          type inet:ip-address;
          description
            "The IP address of the Session-Sender device.
            If not specified, the packets will be sent using
            the sender local network configuration";
        }

        leaf sender-udp-port {
          type union {
            type inet:port-number;
            type enumeration {
              enum autoallocate {
                description
                  "Indicates that the session-sender will
                  auto-allocate the sender-udp-port from the
                  dynamic port range.";
              }
            }
          }
          default "autoallocate";
          description
            "The UDP port number that is to be used by
            the Session-Sender for this TWAMP-Test session";
        }

        leaf reflector-ip {
          type inet:ip-address;
          description
            "The IP address belonging to the remote
            Session-Reflector device to which the TWAMP-Test
            session will be initiated.
            If not specified, the address configured in the peered
            service-session-endpoint will be used.
            If a peered endpoint is not defined or if the peer doesn't
            specify an address, an error will be returned";
        }

        leaf reflector-udp-port {
          type inet:port-number;
          default 862;
          description
            "This parameter defines the UDP port number used by the
            Session-Reflector for this TWAMP-Test session.";
        }

        leaf report-interval {
          type uint16 {
            range "1..900";
          }
          default 30;
          description
            "Reporting interval in seconds";
        }

        leaf reflector-latency-subtraction {
          type boolean;
          default true;
          description
            "Considering T1 as the sender TX timestamp, T4 as the sender
            RX timestamps, T2 as the reflector RX timestamp and T3 as
            the reflector TX timestamps:
            False indicates that the round trip delay measurement is
            calculated with T4-T1.
            True indicates that the round trip delay measurement is
            calculated by substracting the processing time inside the
            session-reflector with (T4-T1) - (T3-T2)";
        }

        container test-packets {

          leaf number-of-packets {
            type union {
              type uint32;
              type enumeration {
                enum continuous {
                  description
                    "The overall number of TWAMP-Test (UDP) packets to be
                    transmitted by the Session-Sender for this test
                    session.";
                }
              }
            }
            default continuous;
            description
              "This value determines the number of packets to transmit during the
              test session.
              Continuous indicates that the packet will be transmitted *forever*";
          }

          leaf payload-size {
            type uint32 {
              range "41..1472";
            }
            default 82;
            description
              "Test packets payload size in bytes";
          }

          leaf rate {
            type uint16 {
              range "1..1000";
            }
            default 10;
            description
              "Test packets transmit rate in PPS";
          }

          leaf dscp {
            type inet:dscp;
            default 0;
            description
              "The DSCP value present in the IP header of the
              TWAMP-Test (UDP) packets";
          }

          leaf ttl {
            type uint8 {
              range "0..255";
            }
            default 255;
            description
              "The Time To Live value present in the IP header of
              the TWAMP-Test (UDP) packets";
          }

          leaf vlan-priority {
            type uint8 {
              range "0..7";
            }
            default 0;
            description
              "Vlan priority. Used when the test packet is sent
              with a vlan tag";
          }
        }
      }

      container session-reflector {
        if-feature "session-reflector";
        description
          "Configuration of the TWAMP Session-Reflector logical entity";

        leaf admin-state {
          type boolean;
          default false;
          description
            "Indicates whether the device is allowed to operate
            as a TWAMP session-reflector";
        }

        leaf reflector-udp-port {
          type inet:port-number;
          default 862;
          description
            "The destination UDP port number used in the
            TWAMP-Test (UDP) test packets belonging to this
            test session.";
        }

        leaf mode {
          type reflector-mode;
          default stateful;
          description
            "The mode of operation of the reflector. Modes are described in the
            reflector-mode type";
        }
      }
    }
  }
}
