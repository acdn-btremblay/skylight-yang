module Accedian-service {
  yang-version 1.1;
  namespace "http://accedian.com/ns/yang/service";
  prefix acdserv;

  import Accedian-type {
    prefix acdt;
  }

  import Accedian-session-type {
    prefix acdst;
  }

  import Accedian-session {
    prefix acdses;
  }

  import Accedian-service-endpoint-type {
    prefix acdsept;
  }

  import Accedian-service-type {
    prefix acdservt;
  }

  import Accedian-extensions {
    prefix acdext;
  }

  organization
    "Accedian Networks Inc.";
  contact
    "Accedian Networks Inc.

    https://accedian.com/
    Email: info@accedian.com

    2351 Blvd Alfred-Nobel, Suite N-410
    Saint-Laurent (Montreal), Quebec,
    H4S 2A9, Canada

    Phone: +1.514.331.6181 or +1.866.685.8181";

  description
    "This module contains the definition of a service.
    Service specific data is added through service type modules. Their
    implementation is contained in modules following the
    format: Accedian-service-<type>.yang. They augment
    the service model when services:type match

    Copyright (c) Accedian Networks, Inc.
    All rights reserved";

  revision 2023-02-10 {
    description
      "Initial revision ";
  }

  notification state-change-event {
    description
      "A top level notification providing state change information on the service and it's
      associated service sessions and service endpoints";

    leaf service-id {
      description
        "The service affected by this state change event. It correspond to
        the service-id of one of the services configured";
      type acdt:id;
    }

    list session-state-change {
      description
        "Each node in this list corresponds to a state change of a service session status. This
        service session is associated with it's parent service. This notification could be
        generate from a state change from the service session itself or from one of its associated
        service-endpoints";
      key session-id;

      leaf session-id {
        description
          "The session identifier. This leaf corresponds to one of the session
          identifier configured in the session list under this service-id.";
        type acdt:id;
      }
      uses acdst:service-session-state-data;

      list service-endpoint-state-change {
        description
          "Each node in this list corresponds to a state change of a service endpoint status. This
          service endpoint is associated with it's parent service and session";
        key endpoint-id;

        leaf endpoint-id {
          description
            "Correspond to the identifier of the service endpoint configured under
            this service service-id/session-id";
          type acdt:id;
        }
        uses acdsept:service-endpoint-state-data;
      }
    }
  }

  rpc delete-service {
    description
      "Delete a service and it's dependencies.
      All the dependencies will be deleted in the proper order
      to avoid broken dependencies.
      By default all associated sessions will be deleted. Service-endpoints
      can also be optionally deleted";

    input {
      container target {
        description
          "The particular service to delete";

        leaf service-id {
          type acdt:id;
          mandatory true;
          description
            "The service-id of the service on which to perform the delete";
        }

        leaf delete-service-endpoints {
          type boolean;
          default false;
          description
            "This leaf indicates if the service-endpoints should also be
            deleted.
            ***Note***: If an endpoint related to this service is
            also refered by another service->session, it will not be deleted";
        }
      }
    }
  }

  container services {
    list service {
      description
        "List of all the services configured";
      key service-id;
      unique service-name;

      leaf service-id {
        type acdt:id;
        acdext:tag-metadata service_id;
        description
          "Id uniquely identifying the service.
          tag-metadata: This leaf will be included as part of the analytics
          metadata as { service_id : <service-id> }";
      }

      leaf service-name {
        type acdt:id;
        acdext:tag-metadata service_name;
        description
          "An optional human readable service name. When provided, the field must
          be unique through all the 'list service' instances.
          'service-name' can be used as an extra metadata query parameter in
          analytics in addition to the service-id. It can also be configured
          to query more easily the analytics when the service-id is in non-human
          readble form (numerical, UUIDs, etc...).
          tag-metadata: This leaf will be included as part of the analytics
          metadata as { service_name : <service-name> }";
      }

    leaf description {
        type string;
        description
          "An optional human readable description for this service";
      }

      leaf type {
        type identityref {
          base acdservt:service;
        }
        description
          "The service deployment type";
        reference
          "supported types are specified in Accedian-service-type.yang";
      }

      container service-definition {
        description
          "Service definition mount point. Service specific data is mounted here through
          Yang augment ation";
      }

      list sessions {
        description
          "The list of sessions involved in this service";
        key session-id;

        leaf session-id {
          description
            "A reference pointing to a pre-existing session. The session is involved in this
            service";
          type leafref {
            path "/acdses:sessions/acdses:session/acdses:session-id";
          }
        }
      }
    }
  }
}
