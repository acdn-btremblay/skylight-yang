module Accedian-twamp-light-capabilities {
  yang-version 1.1;
  namespace "http://accedian.com/ns/yang/session/cap/twamp/light";
  prefix acdtlc;

  import Accedian-session-type {
    prefix acdst;
  }

  import Accedian-service-endpoint {
    prefix acdsep;
  }

  organization
    "Accedian Networks Inc.";
  contact
    "Accedian Networks Inc.

    https://accedian.com/
    Email: info@accedian.com

    2351 Blvd Alfred-Nobel, Suite N-410
    Saint-Laurent (Montreal), Quebec,
    H4S 2A9, Canada

    Phone: +1.514.331.6181 or +1.866.685.8181";

  description
  "This module contains the type definitions of TWAMP-Light capabilities.

    Copyright (c) Accedian Networks, Inc.
    All rights reserved";

  revision 2023-11-24 {
    description
      "Initial revision";
  }

  augment "/acdsep:service-endpoints/acdsep:service-endpoint/acdsep:state/acdsep:capabilities/acdsep:session-capabilities" {
    when "/acdsep:service-endpoints/acdsep:service-endpoint/acdsep:state/acdsep:capabilities/acdsep:session-type = 'acdst:twamp-light'" {

      description
        "Augment Accedian service-endpoint capabilities with twamp-light specific capabilities";
    }

    container twamp-light-capabilities {
      description
        "TWAMP-Light specific capabilities";


      list capability {
        key capability-key;
        description
          "List of key-value where each entry represents a TWAMP-Light capability and it's corresponding
          value. The type of each value is key specific and is described in the key description";

        leaf capability-key {
          description
            "A leaf representing a TWAMP-Light capability. The meaning of each capability and its value
            is described in the following enumeraton";
          type enumeration {
            enum "sender" {
              description
                "Boolean key to indicate if the endpoint can act as a twamp-light sender";
            }
            enum "reflector" {
              description
                "Boolean key to indicate if the endpoint can act as a twamp-light reflector";
            }
            enum "number-of-reflectors" {
              description
                "Integer representing the number of reflector supported by the endpoint. Each extra
                reflector is specified using a different TWAMP reflector port";
            }
          }
        }

        leaf capability-value {
          type acdst:capability-value;
          description
            "The value associated with each TWAMP-Light capability key. The value depends on the
            key. The value type is provided in the key description";
        }
      }
    }
  }
}
