// Contents of "accedian-gateway-orchestrator"
module accedian-gateway-orchestrator {
    yang-version 1.1;
    namespace "urn:accedian:params:xml:ns:yang:accedian-gateway-orchestrator";
    prefix "gateway-orchestrator";

    import ietf-inet-types {
        prefix inet;
        revision-date 2013-07-15;
    }
    import accedian-throughput {
        prefix accedian-throughput;
        revision-date 2021-12-21;
    }

    import accedian-common {
        prefix common;
        revision-date 2021-12-21;
    }

    // import ietf-yang-types {
    // prefix yang;
    // revision-date 2013-07-15;
    // }
    include "accedian-agent-configuration";
    include "accedian-session";
    include "accedian-sensor-control-reflector";
    organization
      "Accedian";

    contact
      "Web URL: https://accedian.com/
       E-mail: info@accedian.com
          Phone:   1.514.331.6181 or +1.866.685.8181";

    description
      "This yang module defines Accedian of skylight components configuration";

    revision 2021-12-21 {
        description
          "Initial Revision";
        reference
          "accedian-gateway-orchestrator";
    }

    typedef agent-state {

        type enumeration {
            enum "configured" {

                description
                  "agent is configured";
            }
            enum "unconfigured" {

                description
                  "agent is un-configured";
            }
        }
        description
          "Defines Agent state";
    }

    typedef agent-status {
        type enumeration {
            enum "connected" {

                description
                  "agent is connected";
            }
            enum "disconnected" {

                description
                  "agent is not connected";
            }
        }
        description
          "Agent state Type";
    }
    typedef agent-type {
        type enumeration {
            enum "actuate" {

                description
                  "Indicate an actuate agent";
            }
            enum "throughput" {

                description
                  "Indicate an throughput agent";
            }
        }
        description
          "Agent Type";
    }

    typedef endpoint-state {
        type enumeration {
            enum "resolved" {

                description
                  "endpoint is resolved";
            }
            enum "terminated" {

                description
                  "agent is terminated";
            }
        }
        description
          "Endpoint state Type";
    }

    typedef endpoint-type {
        type enumeration {
            enum "reflector" {

                description
                  "Indicate an reflector endpoint";
            }
            enum "supervision" {

                description
                  "Indicate an reflector supervision";
            }
            enum "all" {

                description
                  "Indicate can support both";
            }
        }
        description
          "Agent Type";
    }

    typedef endpoint-interface-type {
        type enumeration {
            enum "Ether" {

                description
                  "Indicate Ethernet Interface endpoint";
            }
            enum "VCE" {

                description
                  "Indicate VCE  interface endpoint";
            }
            enum "VLAN" {

                description
                  "Indicate VLAN  interface endpoint";
            }
        }
        description
          "Interface Type";
    }
    typedef supportedActionByEndpoint {

        type enumeration{
            enum start {
                description
                  "start endpoint";
            }

            enum acquire {
                description
                  "start endpoint";
            }

            enum resolve {
                description
                  "resolve endpoint";
            }

            enum terminate {
                description
                  "terminate endpoint";
            }
        }
        description
          "supported action by endpoint";
    }

    container accedian-components {
        description
          "Top level container to represent Accedian sensor components";

        container sensor-agent {
            description
              "This is the root level container for Skylight sensor agent, agent configuration and agent session";

            container agents {
                description
                  "Root Level data container for skylight agents";

                list agent {

                    key agentId;
                    unique agentName;
                    description
                      "List of Agents configured in system";
                    leaf agentId {
                        type string;
                        description
                          "Indicate the unique agent id for the agent";
                    }
                    leaf agentName {
                        type string;
                        mandatory true;
                        description
                          "Indicate the unique agent’s name for the agent";
                    }
                    leaf state {
                        type agent-state;
                        config false;
                        description
                          "Indicate the state of the agent";
                    }
                    leaf status {
                        type agent-status;
                        config false;
                        description
                          "Indicate the status of the agent";
                    }
                    leaf agentType {
                        type agent-type;
                        description
                          "Indicate the type of the agent";
                    }

                    uses agentconfiguration-group;
                }
                action operateAgent {
                    description
                      "operation to be performed on Agent";

                    input {
                        leaf actionName {

                            type common:supportedActionbySession;
                            default run;
                            description
                              "Name of the action to be invoked";
                        }

                        leaf agentId {
                            type leafref {
                                path "/accedian-components/sensor-agent/agents/agent/agentId";
                            }
                            description
                              " Agent Id to locate the session";
                        }
                        list sessions {
                            key sessionId;
                            description
                              "List of Sensor Agent Sessions";
                            leaf sessionId {
                                type leafref {
                                    path "/sessions/session/sessionIdentifier";
                                }
                                description
                                  " Session Id to locate the session";
                            }
                            leaf type {
                                type common:agent-arg-type;
                                description
                                  "operate agent argument type";
                            }
                            // override container with all parms -- sessionType Enum to be mapped , throughput to take from accedian throughput
                            container overrides {
                                description
                                  "overrides agent session at runtime ";
                                leaf ifStateful {
                                    type boolean;
                                    description
                                      "Indicates if the session mode is stateful or stateless";
                                }

                                leaf sessionType {
                                    type common:session-type;
                                    mandatory true;
                                    description
                                      "Session Type to execute the command";
                                }
                                container throughput {
                                    description
                                      "Top level container for Throughput configuration";

                                    uses accedian-throughput:throughput-group;
                                }
                            }
                        }
                    }
                }
            }
        }

        container sensor-control {

            description
              "This is the root level container for Skylight sensor control and control session";

            container endpoints {
                description
                  "Root Level data container for skylight control endpoints";
                list endpoint {
                    key "name type";
                    description
                      "Represents an endpint where service terminates";

                    uses endPointsCommonAttribute-group;

                    container interfaces {
                        config false;
                        description
                          " Intefaces for the endpoints";
                        list interface {
                            key name;
                            description
                              "List of interfaces for sensor control endpoints";
                            leaf name {
                                type string;
                                description
                                  "name of Interface";
                            }
                            leaf type {
                                type endpoint-interface-type;
                                description
                                  "type of Interface";
                            }

                            leaf mac {
                                type common:mac;
                                description
                                  "mac of the endpoint";
                            }
                            list ipaddress {
                                key ip;
                                description
                                  " list of Ip addresses";

                                leaf ip {
                                    type string;
                                    description
                                      "interface IP Address";
                                }
                            }
                        }
                    }

                    container reflector {

                        when "/accedian-components/sensor-control/endpoints/endpoint[name=current()/../name]/type='reflector'";
                        uses endpoint-reflector;
                        description
                          "reflector configuration parameters on endpoint";
                    }
                }

                action operateControl {
                    description
                      "operations to be performed on endpoint";

                    input {
                        leaf actionName {
                            type supportedActionByEndpoint;
                            description
                              "Name of the action to be triggered";
                        }
                        leaf name {
                            type leafref {
                                path "/accedian-components/sensor-control/endpoints/endpoint/name";
                            }
                            description
                              " endpoint connected with the session";
                        }
                    }
                }
            }
        }
    }

    grouping endPointsCommonAttribute-group {
        description
          "endpoint common attribute group";

        leaf name {
            type string;
            mandatory true;
            description
              "Name of the endpoint";
        }

        leaf ip-address {
            type inet:ip-address;
            mandatory true;
            description
              "endpoint IP address";
        }

        leaf description {
            type string;
            description
              "Description of endpoint";
        }
        leaf type {
            type endpoint-type;
            description
              "type of endpoint";
        }

        leaf mac {
            type common:mac;
            description
              "mac address of the endpoint";
        }

        leaf product {
            type common:endpoint-product-type;
            mandatory true;
            description
              "Product type of the endpoint";
        }

        leaf serial-no {
            type string;
            description
              "serial number of the endppoint";
        }

        leaf state {
            type common:endpoint-State;
            config false;
            description
              "state of the endpoint";
        }
        leaf errorInfo {
            type string;
            config false;
            description
              "Information about what caused a error situation, if available.";
        }
    }

    container sessions {
        description
          "Root level container for Sessions";
        uses session-list-group;
    }

    container idGenerator {
        description
          "container to store UUIDs";
        action generateUUID {
            output{
                leaf uuid {
                    type string;
                    description
                      "Generated of UUID";
                }
            }
        }
    }
}
