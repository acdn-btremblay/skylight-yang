module accedian-throughput {

    yang-version 1.1;
    namespace urn:accedian:params:xml:ns:yang:accedian-throughput;
    prefix accedian-throughput;
    import ietf-inet-types {
        prefix inet;
    }

    organization
      "Accedian";

    contact
      "Web URL: https://accedian.com/
       E-mail: info@accedian.com
          Phone:   1.514.331.6181 or +1.866.685.8181";

    description
      "This yang module defines Accedian Throughput session configuration";

    revision 2021-12-21 {
        description
          "Initial Revision";
        reference
          "accedian-throughput : Throughput configuration module";
    }

    grouping throughput-group {
        description
          "Grouping of Throughput parameters";

        leaf testMode {
            type testMode;
            description
              "tetMode for throughput";
        }

        leaf testServerAddress {
            type inet:ip-address;
            default "13.0.0.9";
            description
              "ip address for throughput";
        }
        leaf testServerPort {
            type inet:port-number;
            default "5201";
            description
              "port number for throughput";
        }
        leaf testReverse {
            type  boolean;
            default false;
            description
              "test reverse value for throughput";
        }
        leaf testDurationSecs {
            type  uint32{
                range 1..86400;
            }
            default 60;
            description
              "total duration of throughput test";
        }
        leaf testReportIntervalSecs {
            type decimal64 {
                range 1..60;
                fraction-digits 2;
            }
            default 1.5;
            description
              "test report for interval secs throughput";
        }
        leaf testParallel {
            type  uint32{
                range 1..128;
            }
            default 1;
            description
              "test parallel number for throughput";
        }
        leaf testDscp {
            type inet:dscp;
            default 0;
            description
              "dscp value for throughput";
        }
        leaf testTracerouteDestPort {
            type inet:port-number;
            default "33434";
            description
              "destination port number for throughput";
        }
        leaf networkMaxRateBitsPerSec {
            type  uint32{
                range 0..max;
            }
            default 0;
            description
              "network maximum rate bits per second for throughput";
        }
        leaf networkMtuBytes {
            type  uint32{
                range 0..9000;
            }
            default 1500;
            description
              "network mtu bytes for throughput";
        }
        leaf networkBottleneckBandwidthBitsPerSec {
            type  uint32{
                range 0..max;
            }
            default 161;
            description
              "network bottleneck bandwidth per sec value for throughput";
        }
        leaf networkRttMs {
            type decimal64 {
                fraction-digits 2;
            }
            default 0.44;
            description
              "network RTT in milli seconds for throughput";
        }
    }

    container throughput {
        description
          "properties of throughput test";

        uses throughput-group;
    }

    typedef testMode {
        type enumeration {
            enum "client" {
                description
                  "client test mode";
            }
            enum "server" {
                description
                  "server test mode. In server mode the agent is listening for a connection on the port testServerPort. The agent ignores all other parameters in server mode.";
            }
        }
        description
          "throughput session test mode";
    }
}
