// Contents of "accedian-common"
module accedian-common {
    yang-version 1.1;
    namespace urn:accedian:params:xml:ns:yang:accedian-common;
    prefix "accedian-common";

    // import ietf-yang-types {
    // prefix yang;
    // revision-date 2013-07-15;
    // }
    organization
      "Accedian";

    contact
      "Web URL: https://accedian.com/
       E-mail: info@accedian.com
         Phone:   1.514.331.6181 or +1.866.685.8181";

    description
      "This yang moudule defines common configuration for different skylight components ";

    revision 2021-12-21 {
        description
          "Initial Revision";
        reference
          "accedian-common : common data types and grouping ";
    }

    grouping type_id_rev {
        leaf type {
            type resource-type;
            description
              "Type of the resource";
        }
        leaf id {
            type string;

            description
              "Unique request id for the resource";
        }
        leaf _rev {
            type string;
            config false;
            description
              "Indicate the revision number for the request";
        }
        description
          "grouping of Id, Type and revision attributes to define a reource uniquely";
    }
    typedef _rev {
        type string;
        description
          "Indicate the revision number for the request";
    }

    typedef version {
        type string;
        description
          "Indicate the version of the container";
    }

    typedef session-type {
        type enumeration {
            enum "twamp" {

                description
                  "twamp Session";
            }

            enum "throughput" {

                description
                  "throughput session";
            }

            enum "trace" {

                description
                  "trace session";
            }

            enum "ethoam" {

                description
                  "ethoam session";
            }

            enum "echo" {

                description
                  "echo session";
            }
        }
        description
          "Session Type";
    }

    typedef reflector-type {
        type enumeration {
            enum "twampIpv4" {

                description
                  "twampIpv4 Reflector";
            }

            enum "twampIpv6" {

                description
                  "twampIpv6 Reflector";
            }
            enum "echoUdpIpv4" {

                description
                  "echoUdpIpv4 Reflector";
            }
            enum "echoUdpIpv6" {

                description
                  "echoUdpIpv6 Reflector";
            }
            enum "echoIcmpIpv4" {

                description
                  "echoIcmpIpv4 Reflector";
            }
            enum "echoIcmpIpv6" {

                description
                  "echoIcmpIpv6  Reflector";
            }
			enum "throughput" {

                description
                  "throughput  Reflector";
            }
        }
        description
          "reflector Type";
    }

    typedef agent-state {
        type enumeration {
            enum "unconnected" {

                description
                  "Indicate the state is unconnected";
            }
            enum "connected" {

                description
                  "Indicate the state is connected";
            }
        }
        description
          "agent-state";
    }
    typedef agent-status {
        type enumeration {
            enum "configured" {

                description
                  "configured";
            }
            enum "waiting" {

                description
                  "waiting";
            }
            enum "running" {

                description
                  "running";
            }
        }
        description
          "agent-state";
    }

    typedef agent-arg-type {
        type enumeration {
            enum "baseline" {

                description
                  "baseline type for operate agent argument";
            }
            enum "throughput" {

                description
                  "throughput type for operate agent argument";
            }
        }
        description
          "agent-arg-type enums for operate agent";
    }

    typedef resource-type {
        type enumeration {
            enum "agents" {
                description
                  "agents resource type";
            }
            enum "agentConfigs" {
                description
                  "agent config resource type";
            }
            enum "agentCommands" {
                description
                  "agent commands resource type";
            }
            enum "agentSessions" {
                description
                  "agent session resource type";
            }
            enum "sessionStatuses" {
                description
                  "agent session status resource type";
            }
        }
        description
          "resource-type";
    }

    typedef supportedActionbySession {

        type enumeration{
            enum start {
                description
                  "start session action";
            }
            enum stop {
                description
                  "stop session action";
            }
            enum run {

                description
                  "run command";
            }
            enum terminate {
                description
                  "terminate session action";
            }
        }
        description
          "supported action by session";
    }

    typedef orchestratorType {

        type enumeration{
            enum agent {
                description
                  "Agent Orchestrator";
            }
            enum control {
                description
                  "Control orchestrator";
            }
        }
        description
          "Orchestrator Type";
    }

    // control orchestrator part
    typedef endpoint-State {

        type enumeration {
            enum "NotResolved" {

                description
                  "indicates the state is not resolved";
            }
            enum "Connected" {

                description
                  "indicates the state is connected";
            }

            enum "Error" {

                description
                  "indicates the state is in error state";
            }

            enum "NotConnected" {

                description
                  "indicates the state is not connected";
            }

            enum "Engaged" {

                description
                  "indicates the state is engaged";
            }
        }
        description
          "State of an Endpoint";
    }

    typedef endpoint-product-type {

        type enumeration {
            enum "P2770" {

                description
                  "Product type P2770";
            }
            enum "Ant" {

                description
                  "Product type Ant";
            }
            enum "Ant2Combo" {

                description
                  "Product type Ant2Combo";
            }
            enum "Ant2Copper" {

                description
                  "Product type Ant2Copper";
            }
            enum "NanoNID" {

                description
                  "Product type NanoNID";
            }
            enum "Nano2Copper" {

                description
                  "Product type Nano2Copper";
            }

            enum "Nano2Optical" {

                description
                  "Product type Ant";
            }
            enum "2xOneWay-RF" {

                description
                  "Product type 2xOneWay-RF";
            }

            enum "MetroNID" {

                description
                  "Product type MetroNID";
            }
            enum "MetroNode" {

                description
                  "Product type MetroNode";
            }
            enum "EtherNID" {

                description
                  "Product type EtherNID";
            }
            enum "MetroProbeGT" {

                description
                  "Product type MetroProbeGT";
            }
            enum "HeadEnd" {

                description
                  "Product type HeadEnd";
            }

            enum "Server" {

                description
                  "Product type Server";
            }
            enum "Host" {

                description
                  "Product type Host";
            }
            enum "Router" {

                description
                  "Product type Router";
            }
            enum "Switch" {

                description
                  "Product type Switch";
            }

            enum "CPE" {

                description
                  "Product type CPE ";
            }

            enum "VCX-VNID" {

                description
                  "Product type VCX-VNID ";
            }
        }
        description
          "Product type an Endpoint";
    }

    typedef session-stream-type {

        type enumeration {
            enum "GRE" {

                description
                  "indicates GRE media type";
            }
            enum "ICMP" {

                description
                  "indicates ICMP media type";
            }
            enum "RTP" {

                description
                  "indicates RTP media type";
            }
            enum "SCTP" {

                description
                  "indicates SCTP media type";
            }
            enum "TCP" {

                description
                  "indicates TCP media type";
            }
            enum "UDP" {

                description
                  "indicates UDP media type";
            }
        }
        description
          "List of session stream media type";
    }

    typedef ethoam-session-stream-type {
        type enumeration {
            enum "ETH-DM" {

                description
                  "indicates ETH-DM media type";
            }
            enum "ETH-LB" {

                description
                  "indicates ETH-LB media type";
            }
            enum "ETH-VS" {

                description
                  "indicates ETH-VS media type";
            }
        }
    }

    typedef session-direction {

        type enumeration {
            enum "r2p" {

                description
                  "Direction towards Reflector";
            }
            enum "p2r" {

                description
                  "Direction from Reflector";
            }
            enum "rt" {

                description
                  "Direction round trip";
            }
        }
        description
          "Indicates the direction of the communication from reflector";
    }

    typedef addressFamily {

        type enumeration {
            enum "ipv4" {

                description
                  "IPV4 type IP address";
            }
            enum "ipv6-global" {

                description
                  "IPV6-global IP address";
            }
            enum "ipv6-local" {

                description
                  "IPV6-local IP address";
            }
        }
        description
          "Indicates the addressFamily";
    }
    typedef mac {
        type string{
            pattern
              '[0-9a-fA-F]{2}(:[0-9a-fA-F]{2}){5}';
        }
        description
          "Mac address of the endpoint";
    }

    typedef session-State {

        type enumeration {

            enum "NotResolved" {
                description
                  "indicates the state Not resolved";
            }

            enum "Waiting" {

                description
                  "indicates the state Waiting";
            }

            enum "Running" {

                description
                  "indicates the state Running";
            }

            enum "Ready" {
                description
                  "indicates the state Ready";
            }

            enum "Collecting" {
                description
                  "indicates the state Collecting";
            }

            enum "Terminated" {
                description
                  "indicates the state Terminated";
            }

            enum "Booting" {
                description
                  "indicates the state Booting";
            }

            enum "Error" {
                description
                  "indicates the state Error";
            }
        }
        description
          "State of an Session";
    }

    grouping meta-data {
        list metadata {
            description
              "List of meta data";
            key keyName;
            leaf keyName {
                type "string";
                description
                  "KeyName of the meta data list";
            }
            leaf value {
                type "string";
                description
                  "value of the meta data list entry";
            }
        }
    }
}
