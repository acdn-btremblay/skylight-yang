module accedian-notifications {
    yang-version 1.1;
    namespace "urn:accedian:params:xml:ns:yang:accedian-notifications";
    prefix accnf;

    import ietf-yang-types {
        prefix yang;
        revision-date 2013-07-15;
    }
    import ietf-inet-types {
        prefix inet;
        revision-date 2013-07-15;
    }
    import accedian-metadata {
        prefix accedian-metadata;
        revision-date 2021-12-21;
    }
    import accedian-gateway-orchestrator {
        prefix gateway-orchestrator;
        revision-date 2021-12-21;
    }

    organization
      "Accedian";

    contact
      "Web URL: https://accedian.com/
       E-mail: info@accedian.com
          Phone:   1.514.331.6181 or +1.866.685.8181";

    description
      "This yang module defines Accedian Alert message for Analytics";

    revision 2022-01-04 {
        description
          "Initial Revision";
        reference
          "accedian-alert : Alert configuration";
    }

    typedef alert-state {

        type enumeration {
            enum "raised" {

                description
                  "Alert is Raised";
            }

            enum "error" {

                description
                  "Alert is in error";
            }
            enum "cleared" {

                description
                  "Alert is closed";
            }
            enum "forced-clear" {

                description
                  "Alert is forced-clear";
            }
        }
        description
          "Possible state of an alert";
    }

    typedef object-type {

        type enumeration {
            enum "twamp-sf" {

                description
                  "twamp-sf object";
            }
        }
        description
          "Possible state of an alert";
    }

    typedef securityState {
        type enumeration{
            enum "new" {
                description
                  "state is New";
            }
        }
        description
          "defined security State";
    }
    typedef policy-type {

        type enumeration {
            enum "micro-tca" {

                description
                  "micro-tca alert policy type";
            }
            enum "anomaly" {

                description
                  "anomaly alert policy type";
            }
            enum "capture" {

                description
                  "capture alert policy type";
            }
            enum "security" {

                description
                  "security alert policy type";
            }
            enum "capture-v2" {

                description
                  "capture-v2 alert policy type";
            }
            enum "percentage-violations" {

                description
                  "percentage-violations alert policy type";
            }
        }
        description
          "Possible types of alert policy";
    }

    grouping condition-metric {
        container metric {
            leaf id {
                type string;
                description
                  "identifier of the metric";
            }
            leaf type {
                type accedian-metadata:metric-type;
                description
                  "metric type";
            }
            leaf layer {
                type string;
                description
                  "Capture field name";
            }
            leaf vendor {
                type string;
                description
                  "Vendor name associated with the monitored object";
            }
            leaf-list objectType {
                type string;
                description
                  "Object types to be considered as part of the filter";
            }
            leaf-list direction {
                type string;
                description
                  "Set of one or more directions to be used by the filter to identify required metric records";
            }

            description
              "Metric of the alert condition";
        }
        description
          "Group of node to define Metric";
    }
    grouping alertCondition {
        leaf duration {
            type string;
            default 'PT5M';
            description
              "duration of the metric";
        }

        uses condition-metric;

        leaf ratioPercent {
            type uint8;
            description
              "ratio of condition";
        }

        leaf value {
            type string;
            description
              "Value of the threshold";
        }

        leaf displayUnit {
            type string;
            description
              "Field for UI to perform visual only unit conversions in the front end";
        }

        leaf-list values {
            type string;
            description
              "list of value in conditions";
        }

        leaf comparator {
            type accedian-metadata:comparator;
            default 'eq';
            description
              "comparator filed";
        }

        list blacklist {
            when "../metric/type='security'";
            key field;
            leaf field {
                type string;
                description
                  "blacklist field";
            }
            leaf value {
                type string;
                mandatory true;
                description
                  "blacklist value";
            }
            leaf description {
                type string;
                default "";
                description
                  "blacklist description";
            }
            description
              "blacklist list of conditions";
        }

        list whitelist {
            key id;
            leaf id {
                type string;
                description
                  "id for condition whitelist";
            }

            leaf-list relatedPolicies {
                type string;
                description
                  "list of related policies";
            }

            list triggerConditions {
                key key;
                leaf key {
                    type string;
                    mandatory true;
                    description
                      "key for trigger conditions";
                }
                leaf description {
                    type string;
                    default "";
                    description
                      "description for trigger conditions";
                }
                leaf includes {
                    type boolean;
                    default true;
                    description
                      "includes value for trigger conditions";
                }
                leaf-list values {
                    type string;
                    description
                      "list of values triggerConditions";
                }
                description
                  "trigger conditions for whitelist";
            }

            container workingHours {
                presence
                  true;
                leaf id {
                    type string;
                    description
                      "id for condition workingHours";
                }
                list items {
                    key index;
                    leaf index {
                        type uint8;
                        description
                          "index for working hours items";
                    }
                    container weekly {
                        leaf monday {
                            type boolean;
                            description
                              "monday working values";
                        }
                        leaf tuesday {
                            type boolean;
                            description
                              "tuesday working values";
                        }
                        leaf wednesday {
                            type boolean;
                            description
                              "wednesday working values";
                        }
                        leaf thursday {
                            type boolean;
                            description
                              "thursday working values";
                        }
                        leaf friday {
                            type boolean;
                            description
                              "friday working values";
                        }
                        leaf saturday {
                            type boolean;
                            description
                              "saturday working values";
                        }
                        leaf sunday {
                            type boolean;
                            description
                              "sunday working values";
                        }
                        description
                          "working weekdays condition for whitelist items";
                    }
                    container timeRange {
                        leaf working24h {
                            type boolean;
                            default true;
                            description
                              "working24h values";
                        }
                        container from {
                            leaf hour {
                                type uint8{
                                    range 0..23;
                                }
                                description
                                  "from hour time of working hours";
                            }
                            leaf minute {
                                type uint8{
                                    range 0..59;
                                }
                                description
                                  "from minute time of working hours";
                            }
                            description
                              "working hour From time ";
                        }

                        container to {
                            leaf hour {
                                type uint8{
                                    range 0..23;
                                }
                                description
                                  "to hour time of working hours";
                            }
                            leaf minute {
                                type uint8{
                                    range 0..59;
                                }
                                description
                                  "to minute time of working hours";
                            }
                            description
                              "working hour To time ";
                        }
                        description
                          "working hours range for whitelist conditions";
                    }
                    description
                      "list of items in working hours";
                }

                description
                  "working hours condition for whitelist";
            }

            description
              "Alert policy whitelist condition parameters";
        }

        list advancedFilter {
            key key;
            leaf key {
                type string;
                mandatory true;
                description
                  "key for advance filters";
            }
            leaf includes {
                type boolean;
                default true;
                description
                  "boolean value include";
            }
            leaf-list values {
                type string;
                description
                  "list of values for advance filter";
            }
            description
              "advance filter of conditions";
        }

        description
          "group of attributes to define an alert condition";
    }

    container alert-policies {
        description
          "Top level container to hold all defined alert policies";

        list alert-policy {

            key policyId;
            description
              "List of alert policies";

            leaf policyId {
                type string;
                description
                  "policy Id of an alert";
            }

            container attributes {

                leaf policyName {
                    type string{
                        length 1..64;
                    }
                    description
                      "name of the policy";
                }

                leaf policy-description {
                    type string{
                        length 0..512;
                    }
                    description
                      "description about the policy";
                }
                leaf enabled {
                    type boolean;
                    default true;
                    description
                      "if the policy is deleted";
                }
                leaf deleted {
                    type boolean;
                    default false;
                    description
                      "if the policy is enabled";
                }

                leaf useCleanData {
                    type boolean;
                    default true;
                    description
                      "if the policy uses Clean Data";
                }
                leaf useBusyHourOnly {
                    type boolean;
                    default false;
                    description
                      "if the policy is used in Busy Hour Only";
                }
                leaf useMaintenance {
                    type boolean;
                    default true;
                    description
                      "if the policy is used in maintenance";
                }
                leaf tags {
                    type string{
                        length 0..255;
                    }
                    description
                      "Miscellaneous data the user wants to tag this alert with";
                }
                list conditions {
                    key index;
                    leaf index {
                        type uint8;
                        description
                          "index of condition list";
                    }
                    container triggersOn {
                        uses alertCondition;
                        description
                          "Alert triggering condition";
                    }

                    container recoversOn {
                        uses alertCondition;
                        description
                          "Alert recovery condition";
                    }

                    leaf severity {
                        type string;
                        description
                          "alert policy condition severity";
                    }
                    description
                      "alert condition block";
                }

                container configuration {
                    leaf policy-type {
                        type policy-type;
                        default "micro-tca";
                        description
                          "alert policy type";
                    }
                    leaf aggregationGranularity {
                        type string;
                        description
                          "Capture aggregation's granularity. The alert condition's duration must be same or larger than this value.";
                    }

                    leaf severity {
                        type accedian-metadata:severity;
                        description
                          "severity of the alert";
                    }
                    leaf-list mitreTactics {
                        type string;
                        description
                          "mitre Tactics for alert policy configuration.";
                    }
                    list context {
                        key key;
                        leaf key {
                            type string;
                            description
                              "key for filter map items.";
                        }
                        leaf-list values {
                            type string;
                            description
                              "key for filter map items.";
                        }
                        description
                          "generic filter map items for configuration";
                    }

                    description
                      "Policy configuration";
                }

                description
                    "attributes for alert policy";
            
            }
        }
    }

    notification alertNotification {

        description
          "Alert message data structure";
        container alert {

            leaf policyId {
                type leafref{
                    path '/alert-policies/alert-policy/policyId';
                }
                mandatory true;
                description
                  "policy Id to refer against the alert policy";
            }

            leaf policyName {
                type leafref{
                    path '/accnf:alert-policies/accnf:alert-policy/accnf:attributes/accnf:policyName';
                }
                description
                  "policyName linked with the alert";
            }

            leaf policyType {
                type leafref{
                    path '/accnf:alert-policies/accnf:alert-policy/accnf:attributes/accnf:configuration/accnf:policy-type';
                }
                description
                  "policyName linked with the alert";
            }

            leaf alertState {
                type alert-state;

                description
                  "current state of the alert";
            }

            leaf duration {
                type string;
                description
                  "indicates the duration of the alert";
            }

            leaf topology {
                type string;
                description
                  "indicates the topology of the network";
            }

            leaf objectId {
                type string;
                mandatory true;
                description
                  "indicates the objectId against which the alert is created";
            }

            leaf objectName {
                type string;
                description
                  "indicates the objectName against which the alert is created";
            }

            leaf objectType {
                type object-type;
                description
                  "indicates the objectType against which the alert is created";
            }

            leaf source {
                type string;
                description
                  "source of the alert";
            }

            leaf processedTimestamp {
                type yang:date-and-time;
                description
                  "timestamp at which alert is processed";
            }

            leaf startTimestamp {
                type yang:date-and-time;
                description
                  "timestamp at which alert is started";
            }

            leaf timestamp {
                type yang:date-and-time;
                description
                  "timestamp";
            }
            leaf timeInViolation {
                type uint64;
                description
                  "Timeframe for which the alert is violated";
            }

            uses accedian-metadata:tenant;

            leaf uid {

                type yang:uuid;
                description
                  "uuid of the session";
            }

            leaf uri {
                type string;
                description
                  "URI of the alert";
            }
            leaf annotation {
                type string;
                description
                  "annotations of the alert";
            }
            leaf metric {
                type string;
                description
                  "indicates the metric of the alert";
            }

            leaf direction {
                type string;
                description
                  "indicates the direction of the alert";
            }
            leaf tags {
                type string;
                description
                  "Tags on the alert";
            }
            leaf alertValue {
                type string;
                description
                  "Value of the alert";
            }
            leaf comparator {
                type accedian-metadata:comparator;
                default 'gt';

                description
                  "comparator filed";
            }
            leaf sessionId {
                type leafref{
                    path "/gateway-orchestrator:sessions/gateway-orchestrator:session/gateway-orchestrator:sessionIdentifier";
                }
                description
                  "session Id on which the alert is raised";
            }
            leaf bcn {
                type string;
                description
                  "BCN filed";
            }
            leaf bca {
                type string;
                description
                  "BCA filed";
            }
            leaf ip {
                type inet:ip-address;
                description
                  "IP Address";
            }
            leaf captureLayer {
                type string;
                description
                  "Alert Capture layer";
            }
            leaf captureZone {
                type string;
                description
                  "Alert Capture zone";
            }
            leaf captureApplicationId {
                type string;
                description
                  "Capture Application Id";
            }
            leaf captureZoneId {
                type string;
                description
                  "Alert Capture zone Id";
            }
            leaf captureMetaThresholds {
                type string;
                description
                  "Alert Capture MetaThresholds";
            }
            leaf captureMetaValues {
                type string;
                description
                  "Alert Capture MetaValues";
            }
            leaf captureMetaIps {
                type string;
                description
                  "Alert Capture MetaIps";
            }
            leaf captureMetaDesc {
                type string;
                description
                  "Alert Capture Meta Description";
            }
            leaf captureMetaDate_stop {
                type yang:date-and-time;
                description
                  "Alert Capture Metadata Stop date";
            }
            leaf captureMetaDate_start {
                type yang:date-and-time;
                description
                  "Alert Capture Metadata Start date";
            }
            leaf captureMetaIp_client {
                type string;
                description
                  "Alert Capture Metadata client Id";
            }
            leaf captureMetaIp_count {
                type uint32;
                description
                  "count if IP";
            }
            leaf captureMetaStart {
                type uint32;
                description
                  "Start time of Metadata capture";
            }
            leaf captureMetaStop {
                type uint32;
                description
                  "Stop time of Metadata capture";
            }
            leaf captureMetaName {
                type string;
                description
                  "Name filed";
            }
            leaf captureMetaAlert_id {
                type uint32;
                description
                  "Metadata alert Id";
            }
            leaf captureMetaNow {
                type uint32;
                description
                  "Metadata now";
            }
            leaf captureMetaFirst_sent {
                type uint32;
                description
                  "Metadata First sent";
            }
            leaf captureMetaLast_sent {
                type uint32;
                description
                  "Metadata Last sent";
            }

            leaf captureMetaSite {
                type string;
                description
                  "Metadata Site Id";
            }
            leaf captureMetaWorker {
                type string;
                description
                  "Metadata worker Id";
            }
            leaf captureMetaFiring {
                type string;
                description
                  "Metadata Firing";
            }
            leaf captureMetaCertainty {
                type uint32;
                description
                  "Metadata certainity";
            }
            leaf captureMetaCertainty_percent {
                type string;
                description
                  "Metadata certainity percentage";
            }
            leaf captureClientZoneId {
                type string;
                description
                  "Metadata capture Client ZoneId";
            }
            leaf captureServerZoneId {
                type string;
                description
                  "Metadata capture Server ZoneId";
            }
            leaf severity {
                type accedian-metadata:severity;
                description
                  "severity of the alert";
            }

            leaf sourceIp {
                type inet:ip-address;
                description
                  "Source IP Address";
            }
            leaf sourcePort {
                type inet:port-number;
                description
                  "Source port";
            }

            leaf destinationIp {
                type inet:ip-address;
                description
                  "destination IP Address";
            }
            leaf destinationPort {
                type inet:port-number;
                description
                  "destination port";
            }

            leaf killchain {
                type accedian-metadata:killchain;
                description
                  "kill chain";
            }
            leaf securityJobType {
                type string;
                description
                  "Security Job Type";
            }
            leaf sourceNetworkAssetRoles {
                type string;
                description
                  "source Network Asset Roles";
            }
            leaf destinationNetworkAssetRoles {
                type string;
                description
                  "destination Network Asset Roles";
            }
            leaf securityState {
                type securityState;
                description
                  "security State of alert";
            }

            description
              "Alert container";
        }
    }
}
