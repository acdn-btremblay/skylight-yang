module accedian-metadata {
    yang-version 1.1;
    namespace urn:accedian:params:xml:ns:yang:accedian-metadata;
    prefix accedian-metadata;

    organization
      "Accedian";

    contact
      "Web URL: https://accedian.com/
       E-mail: info@accedian.com
          Phone:   1.514.331.6181 or +1.866.685.8181";

    description
      "This yang module defines Accedian Metadata configuration for Analytics";

    revision 2021-12-21 {
        description
          "Initial Revision";
        reference
          "accedian-metadata : Metadata configuration";
    }
    typedef severity {
        type enumeration{
            enum "informational" {
                description
                  "severity is informational";
            }
            enum "low" {
                description
                  "severity is low";
            }
            enum "medium" {
                description
                  "severity is medium";
            }
            enum "high" {
                description
                  "severity is high";
            }
            enum "critical" {
                description
                  "severity is critical";
            }
        }
        description
          "defined severity in system";
    }
    typedef comparator {
        type enumeration{
            enum "gt" {
                description
                  "grater than";
            }
            enum "lt" {
                description
                  "lesser than";
            }
            enum "eq" {
                description
                  "equal";
            }
            enum "gte" {
                description
                  "grater than equal";
            }
            enum "lte" {
                description
                  "lesser than equal";
            }
            enum "in" {
                description
                  "in condition";
            }
        }

        description
          "defined comparator";
    }
    typedef metric-type {
        type enumeration{
            enum "session" {
                description
                  "Metric type session";
            }

            enum "capture" {
                description
                  "Metric type capture";
            }

            enum "security" {
                description
                  "Metric type security";
            }
        }
        description
          "Metric Type definition";
    }

    typedef killchain {

        type enumeration {
            enum "ActionsOnObjective" {

                description
                  "Killchain : Actions on Objective";
            }
            enum "CommandAndControl" {

                description
                  "Killchain : Command And Control";
            }
            enum "Exfiltration" {

                description
                  "Killchain : Ex filtration";
            }
            enum "Exploitation" {

                description
                  "Killchain : Exploitation";
            }
            enum "Reconnaissance" {

                description
                  "Killchain : Reconnaissance";
            }
        }
        description
          "Killchain of an alert";
    }

    typedef origin-type {
        type enumeration{
            enum "unknown" {
                description
                  "unknown type of the origin of the Monitored Object";
            }

            enum "accedian-nid" {
                description
                  "accedian-nid type of the origin of the Monitored Object";
            }

            enum "accedian-vnid" {
                description
                  "accedian-vnid type of the origin of the Monitored Object";
            }
        }
        description
          "Type of the origin of the Monitored Object";
    }

    typedef  MonitoredObjectType {
        type enumeration{
            enum "unknown" {
                description
                  "unknown type of the origin of the Monitored Object";
            }

            enum "flowmeter" {
                description
                  "flowmeter type of Monitored Object";
            }

            enum "twamp-pe" {
                description
                  "twamp-pe type of Monitored Object";
            }

            enum "twamp-sf" {
                description
                  "twamp-sf type of Monitored Object";
            }

            enum "twamp-sl" {
                description
                  "twamp-sl type of Monitored Object";
            }

            enum "cisco-interface" {
                description
                  "cisco-interface type of Monitored Object";
            }

            enum "cisco-node-summary" {
                description
                  "cisco-node-summary type of Monitored Object";
            }

            enum "pvx" {
                description
                  "pvx type of Monitored Object";
            }

            enum "paa" {
                description
                  "paa type of Monitored Object";
            }

            enum "regulator" {
                description
                  "regulator type of Monitored Object";
            }

            enum "rfc8321" {
                description
                  "rfc8321 type of Monitored Object";
            }

            enum "dmm" {
                description
                  "dmm type of Monitored Object";
            }

            enum "slm" {
                description
                  "slm type of Monitored Object";
            }

            enum "eth-dm" {
                description
                  "eth-dm type of Monitored Object";
            }

            enum "eth-vs" {
                description
                  "eth-vs type of Monitored Object";
            }

            enum "port" {
                description
                  "port type of Monitored Object";
            }

            enum "sa" {
                description
                  "sa type of Monitored Object";
            }

            enum "sa-metrics" {
                description
                  "sa type of Monitored Object";
            }

            enum "pl" {
                description
                  "pl type of Monitored Object";
            }

            enum "iperf" {
                description
                  "iperf type of Monitored Object";
            }

            enum "echo-icmp" {
                description
                  "echo-icmp type of Monitored Object";
            }

            enum "echo-udp" {
                description
                  "echo-udp type of Monitored Object";
            }
        }
        description
          "Type of the origin of the Monitored Object";
    }

    grouping location {
        leaf latitude {
            // type uint32; // -90 to +90 range : how to define
            type decimal64 {

                fraction-digits 2;
            }
            description
              "Latitude of the site";
        }

        leaf longitude {
            // type uint32; // -90 to +90 range : how to define
            type decimal64 {

                fraction-digits 2;
            }
            description
              "longitude of the site";
        }
        description
          "Group of attributes to represent a location";
    }

    grouping tenant {
        leaf tenantId {

            type string;
            config false;
            description
              "Tenant Id from which the alert is raised";
        }

        leaf tenantName {
            type string;
            config false;
            description
              "Tenant name from which the alert is raised";
        }
        description
          "group of attributes to define a Tenant";
    }

    container metadata {
        description
          "Top level container to represent metadata associated with monitored objects";
        list monitoredObject {
            key objectId;
            leaf objectId {
                type string;
                mandatory true;
                description
                  "Object ID to tag with the monitored object session";
            }
            leaf objectName {
                type string;
                mandatory true;
                description
                  "Object Name to tag with the monitored object session";
            }
            leaf actuatorName {
                type string;
                default "";
                description
                  "Name of the origin of the Monitored Object";
            }
            leaf actuatorType {
                type union {
                  type origin-type;
                  type string;
                }
                default "";
                description
                  "Type of the origin of the Monitored Object";
            }
            leaf reflectorName {
                type string;
                default "";
                description
                  "Name of the target of the Monitored Object";
            }
            leaf reflectorType {
                type union {
                  type origin-type;
                  type string;
                }
                default "";
                description
                  "Type of the target of the Monitored Object";
            }      
            leaf objectType {
                type union {
                    type string;
                    type MonitoredObjectType;
                }
                default "";
                description
                  "Type of the target of the Monitored Object";
            }
            container geo {
                description
                  "Geo metadata";

                container startPoint {
                    uses location;
                    description
                      "denotes starting point of metadata config";
                }

                container endPoint {
                    uses location;
                    description
                      "denotes ending point of metadata config";
                }
            }
            leaf-list topology {
                type string;
                description
                  "list of topology points";
            }
            list metadataElement {
                key name;
                description
                  "List of meta data";
                leaf name {
                    type leafref{
                        path "/metadataCategories/metadataCategory/name";
                    }
                    description
                      "KeyName of the meta data list";
                }
                leaf value {
                    type "string";
                    description
                      "value of the meta data list entry";
                }
            }
            description
              "list of monitored object";
        }
    }
    container metadataCategories {
        description
          "Represents all Metadata category configuration";

        uses tenant;

        list metadataCategory {
            key name;
            description
              "represents metadata category";
            leaf name {
                type string;
                description
                  "name of the metadata category";
            }
            leaf isActive {
                type boolean;
                description
                  "if the metadata category is active or not";
            }
        }
    }
}
