submodule accedian-sensor-control-reflector {
    yang-version 1.1;
    belongs-to "accedian-gateway-orchestrator" {
        prefix "gateway-orchestrator"; // this is prefix of parent module
    }

    import accedian-twamp {
        prefix accedian-twamp;
    }

    organization
      "Accedian";

    contact
      "Web URL: https://accedian.com/
       E-mail: info@accedian.com
          Phone:   1.514.331.6181 or +1.866.685.8181";

    description
      "This yang module defines skylight sensor control reflector configuration";
    revision 2021-12-21 {
        description
          "Initial Revision";
        reference
          "accedian-sensor-control-reflector : Reflector configuration";
    }
    typedef reflector-capability {

        type enumeration {
            enum "twamp-rf" {

                description
                  "twamp-rf supported at Layer 3";
            }
            enum "twamp-sl-rf" {

                description
                  "twamp-sl-rf supported at Layer 3";
            }
            enum "echo-udp-rf" {

                description
                  "echo-udp-rf supported at Layer 3";
            }

            enum "echo-icmp-rf" {

                description
                  "echo-icmp-rf supported at Layer 2";
            }

            enum "ethlb-rf" {

                description
                  "ethlb-rf supported at Layer 2";
            }
            enum "ethdm-rf" {

                description
                  "ethdm-rf supported at Layer 2";
            }
            enum "ethvs-rf" {

                description
                  "ethvs-rf supported at Layer 2";
            }
        }
        description
          "Identifies Layer2, Layer3 capabilities supported by a reflector";
    }
    grouping endpoint-reflector {
        description
          " Endpoint Reflector group of attributes";

        container twampcp {
            description
              "TWAMP control protocol | It can only be applied once the reflector is created";
//  when "/accedian-components/sensor-control/endpoints/endpoint[name=current()/../name]/type='reflector'";
            uses accedian-twamp:twamp-ctrl-client-connection;
        }
        leaf-list capabilities {
            type reflector-capability;
            description
              "list of Capabilities supported by the reflector  | It can only be applied once the reflector is created";
        }
    }
}
