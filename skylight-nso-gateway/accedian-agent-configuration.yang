submodule accedian-agent-configuration {
    yang-version 1.1;
    belongs-to "accedian-gateway-orchestrator" {
        prefix "gateway-orchestrator";
    }

    import accedian-common {
        prefix common;
    }
    import ietf-inet-types {
        prefix inet;
    }

    organization
      "Accedian";

    contact
      "Web URL: https://accedian.com/
       E-mail: info@accedian.com
          Phone:   1.514.331.6181 or +1.866.685.8181";

    description
      "This yang module defines skylight sensor agent configuration";

    revision 2021-12-21 {
        description
          "Initial Revision";
        reference
          "accedian-agent-configuration : agent configuration module";
    }

    grouping agentconfiguration-group {
        description
          "Group of Agent Configuration parameters";

        container agentconfiguration {

            description
              "Represents Agent configuration";
            container dataGateway {
                description
                  "Represents DataGateway configured with the Agent";

                leaf server {
                    type inet:ip-address;
                    mandatory true;
                    description
                      "Data gateway Server IP ";
                }
                leaf port {
                    type uint16 {
                        range 1024..65535;
                    }
                    default 55888;
                    description
                      "indicates port number of Data Gateway";
                }
                leaf dataBrokerUseSsl {
                    type boolean;
                    default true;
                    description
                      "If Data broker uses SSL connection";
                }
                leaf dataBrokerSslAllowSelfsigned {
                    type boolean;
                    default true;
                    description
                      "If Data broker SSL Allows self Signed";
                }
                leaf dataBrokerSslAllowInsecureCerts {
                    type boolean;
                    default true;
                    description
                      "If dara broker SSL allows Insecure contect";
                }

                leaf dataBrokerSslAllowExpiredCerts {
                    type boolean;
                    default true;
                    description
                      "if Data broker allows Expired certificates";
                }
                leaf dataBrokerSslSkipHostnameCheck {
                    type boolean;
                    default true;
                    description
                      "If data Broker Ssl Skip Host name Check";
                }
                leaf pdgMetricsEnabled {
                    type boolean;

                    default false;
                    description
                      "if pdgMetricsEnabled";
                }
                leaf brokerATO {
                    type int32 {
                        range 1..max;
                    }
                    default "5";
                    description
                      "indicates the brokerATO field";
                }
                leaf brokerATOMaxCount {
                     type int32 {
                        range 1..max;
                    }
                    default "2";
                    description
                      "Indicate the brokerATOMaxCount filed";
                }
            }

            container reflector {

                presence
                  "Present if agent need to be configured as session reflector";
                description
                  "Represents TWAMP Reflector";
                list reflectors {

                    key reflectorType;
                    leaf reflectorType {

                        type common:reflector-type;
                        description
                          "Denotes reflector type";
                    }
                    leaf enable {

                        type boolean;
                        default "true";
                        description
                          "Denotes if reflector is enable";
                    }
                    description
                      "Represents one reflector configuration";
                }
            }
            uses common:meta-data;
        }
    }
}
